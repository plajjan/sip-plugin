module sip {

	namespace "urn:opencpe:sip";

	prefix "ocpe-sip";

	organization
	    "Deutsche Telekom AG";

	contact
	    "Landgrabenweg 151
	    53227 Bonn, Germany";

	description
	    "This module defines SIP used in the TeraStream home gateway project.";

	revision "2017-08-09" {
	    description
	        "Version 0.2.0";
	}

	container sip-config {
		description
		 "Configuration for SIP.";

		leaf enabled {
			 description "Enable VOIP";
			type boolean;
			mandatory true;
		}

		list sip-account {
			description
			 "Sip account.";

			key account;

			leaf enabled {
				 description "Enable this account";
				type boolean;
				default "true";
			}
			leaf account {
				 description "Name of the SIP account";
				type string;
			}
			leaf account_name {
				 description "Name of the account";
				type string;
			}
			leaf domain {
				 description "SIP doamin name";
				type string;
			}
			leaf username {
				 description "username";
				type string;
			}
			leaf password {
				 description "password";
				type string;
			}
			leaf authentication_name {
				 description "Name used for authentication on SIP server";
				type string;
			}
			leaf display_name {
				 description "Display name used in Caller Id";
				type string;
			}
			leaf host {
				 description "SIP server registrar host";
				type string;
			}
			leaf port {
				 description "SIP server registrar port";
				type uint32;
				default '5060';
			}
			container outbound {
				leaf proxy {
					 description "SIP outbound proxy";
					type string;
				}
				leaf port {
					 description "SIP outbound proxy port";
					type uint32;
					default '5060';
				}
			}
		}
	}

	list sip-status {
		description "State data about SIP.";
		config false;

		key account;

		leaf account {
			 description "Name of the SIP account";
			type string;
		}
		leaf registered {
			 description "SIP registration status";
			type boolean;
		}
		leaf state {
			 description "SIP connection status";
			type string;
		}
	}
}
